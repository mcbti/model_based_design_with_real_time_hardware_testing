# MOT_CTRL_MOT

## MOT_CTRL-MOT-FUN-001: Relação crescente entre tensão e velocidade angular (Functional)
O modelo do motor deve gerar uma velocidade crescente conforme a tensão de armadura aplicada cresce.
- Rationale: Garante o comportamento físico básico do modelo PMDC, necessário para a coerência funcional com os demais blocos do sistema (PWM e controle).

## MOT_CTRL-MOT-FUN-002: Tempo de resposta do motor a um degrau de tensão (Functional)
O tempo de resposta do modelo do motor, medido do instante de aplicação de um degrau de tensão até o momento em que a velocidade angular atinge 95% do valor final, deve ser inferior a 250 milissegundo.
- Rationale: O tempo de resposta compatível é necessário para estar de acordo com o modelo dos dados coletados em bancada.

## MOT_CTRL-MOT-FUN-003: Limite operacional da velocidade angular (Functional)
A velocidade angular simulada pelo modelo do motor deve estar limitada entre 0 rpm e 5100 rpm para todas as condições de entrada.
- Rationale: Garante que o modelo permaneça dentro dos limites físicos esperados e evita extrapolações que possam comprometer a validação do controle.
