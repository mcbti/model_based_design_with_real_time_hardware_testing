# MOT_CTRL_PWM

## MOT_CTRL_PWM_FUN_001: Geração PWM (Functional)
O sinal PWM deve variar continuamente entre 0 e 5 com precisão double.
- Rationale: Garantir a adequada resolução dos valores do PWM.

## MOT_CTRL_PWM_FUN_002: Frequência do sinal PWM (Functional)
A frequência do sinal PWM deve ser de 1 kHz, com tolerância de 2%.
- Rationale: Garantir a resposta do filtro passa baixa na saída da ponte H.

## MOT_CTRL_PWM_FUN_003: SInal compatível com nível TTL (Functional)
A onda do sinal PWM deve ter amplitude conforme padrao TTL.
- Rationale: Garantir o nível de tensão correta na interface com o driver do motor.
