# MOT_CTRL_PTH

## MOT_CTRL_PTH_CONT_001: Comutação de polaridade conforme entrada de controle (Container)
A ponte H deve comutar a polaridade da tensão de saída aplicada ao motor conforme o sinal de entrada de controle (ex: sentido horário/anti-horário).
- Rationale: Necessário para permitir reversão de rotação no motor.

### MOT_CTRL_PTH_FUN_001_1: Comutação de polaridade positiva (Functional)
A tensão chaveada na saída deve ser positiva quando o sinal de controle for positivo (forward).
- Rationale: Necessário para rotacional no sentido horário.

### MOT_CTRL_PTH_FUN_001_2: Comutação de polaridade negativa (Functional)
A tensão chaveada na saída deve ser positiva quando o sinal de controle for negativo (backward).
- Rationale: Necessário para rotacional no sentido anti-horário.

## MOT_CTRL_PTH_CONT_002: Tempo de comutação entre estados da ponte H (Container)
A ponte H deve realizar a transição completa entre estados de condução (alta/baixa) e o estado desligado em no máximo 250 ms.
- Rationale: Garante resposta rápida à comutação de controle e evita estados de transição longos que podem causar perdas ou instabilidade.

### MOT_CTRL_PTH_FUN_002_1: Tempo de comutação entre estados da ponte H (Functional)
A ponte H deve realizar a transição completa do estado desligado para o estado direto em até 250 ms.
- Rationale: Garante resposta rápida à comutação para rotação no sentido horário.

### MOT_CTRL_PTH_FUN_002_2: Tempo de comutação entre estados da ponte H (Functional)
A ponte H deve realizar a transição completa do estado desligado para o estado reverso em até 250 ms.
- Rationale: Garante resposta rápida à comutação para rotação no sentido horário.

## MOT_CTRL_PTH_CONT_003: Faixa de operação da tensão de saída da ponte H (Container)
A tensão de saída da ponte H aplicada ao motor deve próxima de 336 V no sentido direto, e -336 V no sentido reverso, com toletância de 5%.
- Rationale: IO motor deve operar em torno da faixa nominal para aumento da vida útil.

### MOT_CTRL_PTH_FUN_003_1: Faixa de operação da tensão de saída da ponte H (Functional)
A tensão de saída da ponte H aplicada ao motor deve próxima de 336 V no sentido direto, com toletância de 5%.
- Rationale: IO motor deve operar em torno da faixa nominal para aumento da vida útil.

### MOT_CTRL_PTH_FUN_003_2: Faixa de operação da tensão de saída da ponte H (Functional)
A tensão de saída da ponte H aplicada ao motor deve próxima de 336 V no sentido reverso, com toletância de 5%.
- Rationale: O motor deve operar em torno da faixa nominal para aumento da vida útil
